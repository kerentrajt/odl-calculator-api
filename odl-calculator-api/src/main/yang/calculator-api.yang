module odltests-api {
    yang-version 1;
    namespace "urn:opendaylight:params:xml:ns:yang:odltests:api";
    prefix "odltests-api";

    revision "2017-05-07" {
        description
            "Initial revision for Odl Test Api";
    }

    container odltests-api {
        config true;
        description
            "api for odl test";

        leaf name {
            type string;
            description
               "The name of the interface.";
        }

    }
}
