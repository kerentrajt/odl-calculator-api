module odl-calculator-operational-api {
    yang-version 1;
    namespace "urn:opendaylight:params:xml:ns:yang:odl-calculator-operational-api:api";
    prefix "odl-calculator-api";

    revision "2017-05-07" {
        description
            "Initial revision for Odl Test Api";
    }

    container odl-calculator-openrational-api {
        config true;
        description
            "api for odl test";

        leaf calculator-output{
            type string;
            description
               "The name of the interface.";
    
        }

    }
}
